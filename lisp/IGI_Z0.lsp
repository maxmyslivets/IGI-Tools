(defun c:IGI_Z0 ( / ss oldos oldcm)
  (vl-load-com)

  ;; Скрываем системный вывод команд на время подготовки
  (setq oldcm (getvar "CMDECHO"))
  (setvar "CMDECHO" 0)

  (princ "\n=============================================")
  (princ "\n [IGI] Запуск проверки и обнуления чертежа   ")
  (princ "\n=============================================\n")

  ;; Шаг 1: Проверка ошибок чертежа
  (princ " -> Шаг 1/3: Проверка базы данных (_AUDIT)... ")
  (vl-cmdf "_.audit" "_y")
  (princ "ОК.")

  ;; Шаг 2: Выбор объектов
  (princ "\n -> Шаг 2/3: Сбор геометрии чертежа...         ")
  (setq ss (ssget "_X"))

  (if ss
    (progn
      (princ "ОК.")
      ;; Отключаем привязки перед перемещением
      (setq oldos (getvar "OSMODE"))
      (setvar "OSMODE" 0)

      ;; Шаг 3: Математическое обнуление
      (princ "\n -> Шаг 3/3: Проецирование на плоскость Z=0... ")
      (vl-cmdf "_.move" ss "" "0,0,0" "0,0,1e99")
      (vl-cmdf "_.move" ss "" "0,0,0" "0,0,-1e99")
      (princ "ОК.")

      ;; Возвращаем привязки
      (setvar "OSMODE" oldos)

      ;; Финальный красивый вывод
      (princ "\n\n=============================================")
      (princ (strcat "\n Успешно обработано объектов: " (itoa (sslength ss))))
      (princ "\n Все элементы перенесены на отметку 0.000")
      (princ "\n=============================================\n")
    )
    (progn
      (princ "Ошибка!")
      (princ "\n Объекты для переноса не найдены в файле.")
      (princ "\n=============================================\n")
    )
  )

  ;; Финальное обновление экрана без спама в консоль
  (vla-regen (vla-get-activedocument (vlax-get-acad-object)) acAllViewports)
  (setvar "CMDECHO" oldcm)
  (princ)
)
